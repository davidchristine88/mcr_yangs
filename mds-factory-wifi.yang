module mds-factory-wifi {
  namespace "com:gemds:mds-factory-wifi";
  prefix mdsfactwifi;

  import mds-factory {
    prefix fact;
  }

  organization "GE MDS LLC";
  contact
    "T 1-800-474-0694 (Toll Free in North America)
     T 585-242-9600
     F 585-242-9620
     
     175 Science Parkway
     Rochester, New York 14620
     USA
    ";
  description
    "This module contains factory-only level commands.
     
     Copyright (c) 2017 by GE MDS LLC. All rights reserved.";

  revision 2017-03-15 {
    description
      "Initial revision.";
  }

  augment "/fact:factory" {
    container wifi;
  }
}
