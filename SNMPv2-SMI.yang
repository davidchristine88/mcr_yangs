module SNMPv2-SMI {
  namespace "http://tail-f.com/ns/mibs/SNMPv2-SMI/1.0";
  prefix SNMPv2_SMI;

  import ietf-yang-types {
    prefix yang;
  }

  typedef ExtUTCTime {
    type hex-list;
  }

  typedef ObjectName {
    type yang:object-identifier;
  }

  typedef NotificationName {
    type yang:object-identifier;
  }

  typedef Integer32 {
    type int32 {
      range "-2147483648 .. 2147483647";
    }
  }

  typedef IpAddress {
    type string {
      pattern "(0|[1-9](([0-9]){0,2})).(0|[1-9](([0-9]){0,2})).(0|[1-9](([0-9]){0,2})).(0|[1-9](([0-9]){0,2}))";
    }
  }

  typedef Counter32 {
    type uint32 {
      range "0 .. 4294967295";
    }
  }

  typedef Gauge32 {
    type uint32 {
      range "0 .. 4294967295";
    }
  }

  typedef Unsigned32 {
    type uint32 {
      range "0 .. 4294967295";
    }
  }

  typedef TimeTicks {
    type uint32 {
      range "0 .. 4294967295";
    }
  }

  typedef Opaque {
    type hex-list;
  }

  typedef Counter64 {
    type yang:counter64 {
      range "0 .. 18446744073709551615";
    }
  }

  typedef hex-list {
    type string {
      pattern "(([0-9a-fA-F]){2}(:([0-9a-fA-F]){2})*)?";
    }
    status deprecated;
    description
      "DEPRECATED: Use yang:hex-string instead.  There are no plans to remove
       tailf:hex-list.
       
       A list of colon-separated hexa-decimal octets e.g. '4F:4C:41:71'.
       
       The statement tailf:value-length can be used to restrict the number
       of octets.  Note that using the 'length' restriction limits the
       number of characters in the lexical representation.";
  }
}
