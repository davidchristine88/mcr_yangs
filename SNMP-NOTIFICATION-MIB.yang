module SNMP-NOTIFICATION-MIB {
  namespace "http://tail-f.com/ns/mibs/SNMP-NOTIFICATION-MIB/200210140000Z";
  prefix SNMP_NOTIFICATION_MIB;

  import ietf-yang-types {
    prefix yang;
  }
  import SNMPv2-TC {
    prefix SNMPv2_TC;
  }
  import SNMP-TARGET-MIB {
    prefix SNMP_TARGET_MIB;
  }

  revision 2002-10-14 {
    description
      "";
  }

  container SNMP-NOTIFICATION-MIB {
    container snmpNotifyTable {
      list snmpNotifyEntry {
        key "snmpNotifyName";
        leaf snmpNotifyName {
          type snmpNotifyNameType;
        }
        leaf snmpNotifyTag {
          type SNMP_TARGET_MIB:SnmpTagValue;
        }
        leaf snmpNotifyType {
          type snmpNotifyTypeType;
          default "trap";
        }
        leaf snmpNotifyStorageType {
          type SNMPv2_TC:StorageType;
          default "nonVolatile";
        }
      }
    }
  }

  typedef snmpNotifyNameType {
    type string {
      length "1 .. 32";
    }
  }

  typedef snmpNotifyTypeType {
    type enumeration {
      enum "trap" {
        value 1;
      }
      enum "inform" {
        value 2;
      }
    }
  }

  typedef snmpTargetParamsNameType {
    type string {
      length "1 .. 32";
    }
  }

  typedef snmpNotifyFilterProfileNameType {
    type string {
      length "1 .. 32";
    }
  }

  typedef snmpNotifyFilterMaskType {
    type hex-list {
      pattern "(((([0-9A-Fa-f]{2}):){0,15}([0-9A-Fa-f]{2}))){0,1}";
    }
  }

  typedef snmpNotifyFilterTypeType {
    type enumeration {
      enum "included" {
        value 1;
      }
      enum "excluded" {
        value 2;
      }
    }
  }

  typedef hex-list {
    type string {
      pattern "(([0-9a-fA-F]){2}(:([0-9a-fA-F]){2})*)?";
    }
    status deprecated;
    description
      "DEPRECATED: Use yang:hex-string instead.  There are no plans to remove
       tailf:hex-list.
       
       A list of colon-separated hexa-decimal octets e.g. '4F:4C:41:71'.
       
       The statement tailf:value-length can be used to restrict the number
       of octets.  Note that using the 'length' restriction limits the
       number of characters in the lexical representation.";
  }
}
