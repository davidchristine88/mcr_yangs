module mds-service-nhrp {
  namespace "com:gemds:services:nhrp";
  prefix nhrp;

  import ietf-inet-types {
    prefix inet;
  }
  import mds-services {
    prefix serv;
  }
  import mds-security {
    prefix sec;
  }
  import ietf-interfaces {
    prefix if;
  }

  organization "GE MDS LLC";
  contact
    "T 1-800-474-0694 (Toll Free in North America)
     T 585-242-9600
     F 585-242-9620
     
     175 Science Parkway
     Rochester, New York 14620
     USA
    ";
  description
    "This module contains a collection of YANG definitions for
     configuring and monitoring NHRP service.
     
     Copyright (c) 2015 by GE MDS LLC. All rights reserved.";

  revision 2015-08-14 {
    description
      "Initial.";
  }

  augment "/serv:services" {
    container nhrp {
      leaf enabled {
        type boolean;
        default "false";
        description
          "Whether or not to run NHRP service";
      }
      must "(count(interface) > 0 or enabled = 'false')" {
        error-message "Atleast one interface must be configured in nhrp configuration.";
      }
      list interface {
        key "name";
        leaf name {
          type if:interface-ref;
          description
            "The interface on which the protocol is activated with given interface-specific options.";
        }
        list map {
          description
            "static mapping of protocol-address to nbma-address";
          key "name";
          leaf name {
            type sec:word-string;
            description
              "Name of the mapping. (allowed chars: a-zA-Z0-9-_).";
          }
          leaf protocol-address {
            type inet:ip-address;
            mandatory true;
            description
              "Peer protocol address (i.e. peer tunnel interface address)";
          }
          leaf protocol-netmask {
            type inet:ip-address;
            description
              "Peer protocol address mask. If present, the peer is used a next hop server 
               for the subnet specified by protocol-address and protocol-netmask.";
          }
          leaf nbma-address {
            type inet:host;
            mandatory true;
            description
              "Peer NBMA FQDN or address (i.e. peer transport/nbma network name or address)";
          }
          leaf register {
            type boolean;
            default "false";
            description
              "Registration Request should be sent to this peer on startup.";
          }
          leaf cisco {
            type boolean;
            default "false";
            description
              "Registration Request should be sent to this peer on startup.";
          }
        }
        leaf authentication {
          type aes-cfb-128-encrypted-string;
          description
            "Enables  Cisco style authentication on NHRP packets. This embeds
             the secret plaintext password  to  the  outgoing  NHRP  packets.
             Incoming NHRP packets on this interface are discarded unless the
             secret password is present. Maximum length of the  secret  is  8
             characters.";
        }
        leaf holding-time {
          type uint32;
          default "7200";
          description
            "Specifies  the  holding  time (in secondS) for NHRP Registration Requests and
             Resolution Replies sent from this interface";
        }
        container multicast {
          leaf dynamic {
            type boolean;
            default "true";
            description
              "Multicast traffic is forwarded to all peers with which the interface has a 
               direct connection";
          }
        }
        leaf redirect {
          type boolean;
          default "true";
          description
            "Enables sending of Cisco style NHRP Traffic Indication packets.
             If this is enabled and nhrp detects a forwarded  packet,  it
             will  send  a  message  to  the  original  sender  of the packet
             instructing it to create a direct connection with  the  destina‐
             tion.";
        }
        leaf shortcut {
          type boolean;
          default "true";
          description
            "Enable creation of shortcut  routes.  A  received  NHRP  Traffic
             Indication  will  trigger  the resolution and establishment of a
             shortcut route.";
        }
        leaf shortcut-destination {
          type empty;
          description
            "This  instructs  the device to  reply with authorative answers on
             NHRP Resolution Requests destined to addresses in  this  interface  
             (instead  of  forwarding  the  packets).  This allows the creation 
             of shortcut routes to subnets located on the interface.  
             
             NOTE: When specified, this should be the only parameter 
             configured for this interface.";
        }
      }
      container status {
        config false;
        list entry {
          leaf nbma-address {
            type inet:ip-address;
            description
              "Peer NBMA address.";
          }
          leaf protocol-address {
            type inet:ip-prefix;
            description
              "Peer protocol/tunnel address.";
          }
          leaf state {
            type string;
            description
              "State of entry.";
          }
          leaf type {
            type enumeration {
              enum "local" {
                description
                  "The entry is local.";
              }
              enum "static" {
                description
                  "The entry has been configured statically.";
              }
              enum "dynamic" {
                description
                  "The entry has been learned dynamically.";
              }
              enum "shortcut-route" {
                description
                  "The entry is shortcut route learned via redirect.";
              }
            }
            description
              "Type of entry.";
          }
          leaf expires-in {
            type string;
            description
              "Specifies the duration after which it would expire.";
          }
        }
      }
    }
  }

  typedef aes-cfb-128-encrypted-string {
    type string;
    description
      "The aes-cfb-128-encrypted-string works exactly like
       des3-cbc-encrypted-string but AES/128bits in CFB mode is used to
       encrypt the string.  The prefix for encrypted values is '$4$'.";
  }
}
