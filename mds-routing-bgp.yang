module mds-routing-bgp {
  namespace "com:gemds:mds-routing-bgp";
  prefix mds-routing-bgp;

  import ietf-yang-types {
    prefix yang;
  }
  import ietf-inet-types {
    prefix inet;
  }
  import mds-security {
    prefix sec;
  }
  import mds-routing {
    prefix mds-routing;
  }
  import mds-services {
    prefix serv;
  }
  import mds-service-netmon {
    prefix nmon;
  }

  description
    "This module contains a collection of YANG definitions for
     configuring BGP routing protocol.
     
     Copyright (c) 2016 by GE MDS LLC. All rights reserved.";

  revision 2017-07-03 {
    description
      "Added bgp neighbor monitor.";
  }
  revision 2016-04-15 {
    description
      "Initial Revision";
  }

  grouping bgp-common {
    leaf preference {
      type uint16;
      description
        "Specifies the preference of the routes generated by this protocol.";
    }
  }

  grouping bgp-neighbor-common {
    leaf enabled {
      type boolean;
      default "true";
      description
        "Specifies whether BGP is enabled for this neighbor.";
    }
    leaf import-filter {
      type leafref {
        path "/mds-routing:routing/mds-routing:route-filter/mds-routing:name";
      }
      description
        "Route filter to apply when importing routes into the routing table from this routing protocol.";
    }
    leaf export-filter {
      type leafref {
        path "/mds-routing:routing/mds-routing:route-filter/mds-routing:name";
      }
      description
        "Route filter to apply when exporting routes from the routing table to this routing protocol.";
    }
    leaf passive {
      type boolean;
      default "false";
      description
        "If true, this router will not initiate outgoing connections and will only accept incoming connections.";
    }
    leaf local-as {
      type uint32;
      mandatory true;
      description
        "Local Autonomous System (AS) number.";
    }
    leaf peer-as {
      type uint32;
      mandatory true;
      description
        "Neigbor Autonomous System (AS) number.";
    }
    leaf link-type {
      type enumeration {
        enum "direct" {
          description
            "Indicates that the neighbor is directly connected. The IP address of the neighbor
             must be from a directly reachable IP range (i.e. associated with one of the router's
             interfaces), otherwise the BGP session wouldn't start but it would wait for such interface
             to appear.";
        }
        enum "multihop" {
          description
            "Indicates that the neighbor isn't directly connected. This should be used if the configured
             neighbor IP address does not match with any local network subnets. Such IP address has to be
             reachable through system routing table.";
        }
      }
      description
        "Specifies how this router is connected to the neighbor(s).";
    }
    leaf next-hop-self {
      type boolean;
      default "false";
      description
        "Specifies whether this router's source address is advertised as the next-hop in the Next-Hop attribute.";
    }
    leaf hold-time {
      type uint16;
      default "240";
      units "seconds";
      description
        "Time in seconds to wait for a Keepalive message from the other side before considering the connection stale.";
    }
    leaf keepalive-time {
      type uint16;
      default "80";
      units "seconds";
      description
        "Delay in seconds between sending of two consecutive Keepalive messages.";
    }
    leaf connect-retry-time {
      type uint16;
      default "120";
      units "seconds";
      description
        "Time in seconds to wait before retrying a failed attempt to connect.";
    }
  }

  grouping bgp {
    uses bgp-common;
    list neighbor {
      key "name";
      min-elements 1;
      description
        "Configuration of BGP peer.";
      leaf name {
        type sec:word-string;
        description
          "An ASCII string identifying the neighbor.";
      }
      leaf peer-type {
        type enumeration {
          enum "static" {
            description
              "Neighbor is static with fixed address";
          }
        }
        default "static";
        description
          "Type of neighbor";
      }
      must "peer-address and peer-type = 'static'" {
        error-message "Must configure peer-address for a static neighbor.";
      }
      leaf peer-address {
        type inet:ipv4-address;
        description
          "Neighbor IPv4 address.";
      }
      leaf local-address {
        type inet:ipv4-address;
        description
          "Local/Source IPv4 address to use for session with this neighbor.";
      }
      uses bgp-neighbor-common;
    }
  }

  grouping bgp-state {
    list neighbor {
      key "name";
      leaf name {
        type string;
        description
          "An ASCII string identifying the neighbor.";
      }
      uses mds-routing:protocol-state;
      leaf local-state {
        type enumeration {
          enum "idle";
          enum "connect";
          enum "active";
          enum "open-sent";
          enum "open-confirm";
          enum "established";
          enum "close";
        }
        description
          "Protocol state.";
      }
      leaf peer-address {
        type inet:ip-address;
        description
          "Peer IP address";
      }
      leaf peer-as {
        type uint32;
        description
          "Peer AS.";
      }
      leaf peer-id {
        type yang:dotted-quad;
        description
          "Peer Router ID.";
      }
      leaf local-address {
        type inet:ip-address;
        description
          "Local Address.";
      }
      leaf hold-time {
        type string;
        description
          "Hold time.";
      }
      leaf keepalive-time {
        type string;
        description
          "Keepalive time.";
      }
    }
  }

  augment "/mds-routing:routing" {
    container bgp {
      presence "BGP IPv4 Configuration";
      uses bgp;
      description
        "Configuration of BGP for IPV4.";
    }
  }
  augment "/mds-routing:routing-state" {
    container bgp {
      config false;
      uses bgp-state {
        refine "neighbor";
      }
    }
  }
  augment "/serv:services/nmon:netmon/nmon:operation/nmon:bgp-neighbor-monitor" {
    leaf neighbor {
      type leafref {
        path "/mds-routing:routing/bgp/neighbor/name";
      }
      description
        "BGP neighbor to monitor.";
    }
  }
}
