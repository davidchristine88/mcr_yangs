module mds-routing {
  namespace "com:gemds:mds-routing";
  prefix mds-routing;

  import ietf-yang-types {
    prefix yang;
  }
  import ietf-interfaces {
    prefix if;
  }
  import ietf-inet-types {
    prefix inet;
  }
  import mds-security {
    prefix sec;
  }
  import mds-services {
    prefix serv;
  }
  import mds-service-netmon {
    prefix nmon;
  }
  import mds-service-qos {
    prefix qos;
  }

  organization "GE MDS LLC";
  contact
    "T 1-800-474-0694 (Toll Free in North America)
     T 585-242-9600
     F 585-242-9620
     
     175 Science Parkway
     Rochester, New York 14620
     USA
    ";
  description
    "This module contains a collection of YANG definitions for
     configuring simple routing options.
     
     Copyright (c) 2013 by GE MDS LLC. All rights reserved.";

  revision 2017-07-03 {
    description
      "Added support for multiple routing instances (static routes only).";
  }
  revision 2016-04-15 {
    description
      "Added BGP protocol.";
  }
  revision 2015-05-15 {
    description
      "Refactored data model. Moved several parts into seperate modules.";
  }
  revision 2014-09-11 {
    description
      "Updated verify-reachability field to require netmon operation";
  }
  revision 2014-08-26 {
    description
      "Added preference (a.k.a metric) and verify-reachability
       configuration to routes to enable route failover/failback";
  }
  revision 2013-02-12 {
    description
      "Initial Revision";
  }

  grouping protocol-common {
    leaf enabled {
      type boolean;
      default "true";
      description
        "Specifies whether routing protocol is enabled.";
    }
    leaf preference {
      type uint16;
      description
        "Specifies the preference of the routes generated by this protocol.";
    }
    leaf import-filter {
      type leafref {
        path "/mds-routing:routing/mds-routing:route-filter/mds-routing:name";
      }
      description
        "Route filter to apply when importing routes into the routing table from this routing protocol.";
    }
    leaf export-filter {
      type leafref {
        path "/mds-routing:routing/mds-routing:route-filter/mds-routing:name";
      }
      description
        "Route filter to apply when exporting routes from the routing table to this routing protocol.";
    }
  }

  grouping route-content {
    description
      "Generic parameters of routes.";
    leaf description {
      type string;
      description
        "Textual description of the route.";
    }
    leaf outgoing-interface {
      type if:interface-ref;
      description
        "Outgoing interface.";
    }
    leaf preference {
      type uint32;
      description
        "Preference value of the route (lower value implies higher preference)";
    }
    container verify-reachability {
      presence "verify reachability of the route";
      leaf operation {
        type leafref {
          path "/serv:services/nmon:netmon/nmon:operation/nmon:name";
        }
        mandatory true;
        description
          "The network monitor operation to use for verifying reachability";
      }
    }
  }

  grouping static-routes {
    container ipv4 {
      list route {
        key "id";
        ordered-by user;
        description
          "A user-ordered list of static routes.";
        leaf id {
          type uint32 {
            range "1..max";
          }
          description
            "Numeric identifier of the route.
             
             It is not required that the routes be sorted by their
             'id'.";
        }
        uses route-content;
        leaf dest-prefix {
          mandatory true;
          type inet:ipv4-prefix;
          description
            "IPv4 destination prefix (a.b.c.d/p).";
        }
        leaf next-hop {
          type inet:ipv4-address;
          description
            "IPv4 address of the next hop.";
        }
      }
    }
    container ipv6 {
      list route {
        key "id";
        ordered-by user;
        description
          "A user-ordered list of static routes.";
        leaf id {
          type uint32 {
            range "1..max";
          }
          description
            "Numeric identifier of the route.
             
             It is not required that the routes be sorted by their
             'id'.";
        }
        uses route-content;
        leaf dest-prefix {
          mandatory true;
          type inet:ipv6-prefix;
          description
            "IPv6 destination prefix.";
        }
        leaf next-hop {
          type inet:ipv6-address;
          description
            "IPv6 address of the next hop.";
        }
      }
    }
  }

  container routing {
    description
      "Top-level container for routing configuration and status objects.
       By default, there is always a main routing instance configured implicility
       in the system. And within this main routing instance, the user can configure static
       routes and various supported routing protocols like RIP, OSPF and BGP. These routing
       protocols interact with the routing table assciated with this main routing instance.
       
       The user also can create one or more additional routing instances (i.e. virtual routers).
       These instances are stored in the '/routing/routing-intances' list. Each such instance
       get its own routing table. And within each such routing instance, the user can configure
       static routes and various supported routing protocols like RIP, OSPF and BGP. These routing
       protocols interact with the routing table associated with this routing instance.";
    leaf router-id {
      type yang:dotted-quad;
      description
        "A 32-bit number in the form of a dotted quad that is used by
         some routing protocols to identify a router.";
      reference "RFC 2328: OSPF Version 2.";
    }
    list route-filter {
      description
        "Route filters enable filtering of routes imported/exported into/from routing table
         by the routing protocols.";
      key "name";
      leaf name {
        type sec:word-string;
        description
          "Name assigned to this route filter.";
      }
      list rule {
        key "id";
        min-elements 1;
        max-elements "32";
        leaf id {
          type uint32;
          description
            "ID of the rule. The rules are sorted and applied in the order of inccreasing ids.";
        }
        container match {
          leaf dest-prefix {
            type inet:ip-prefix;
            description
              "Network prefix of the route.";
          }
          leaf source-protocol {
            type enumeration {
              enum "bgp" {
                description
                  "The route as been generated from BGP protocol.";
              }
              enum "ospf" {
                description
                  "The route as been generated from OSPF protocol.";
              }
              enum "rip" {
                description
                  "The route as been generated from RIP protocol.";
              }
            }
            description
              "The protocol that generated this route.";
          }
          leaf source-router {
            type inet:ip-address;
            description
              "The router address from which the route has originated.";
          }
          leaf outgoing-interface {
            type if:interface-ref;
            description
              "The outgoing interface for the route that the protocol is trying to install
               in the routing table.";
          }
          leaf next-hop {
            type inet:ip-address;
            description
              "The next hop for the route that the protocol is trying to install in the routing table.";
          }
        }
        container actions {
          leaf action {
            mandatory true;
            type enumeration {
              enum "accept" {
                description
                  "Accept the route update";
              }
              enum "reject" {
                description
                  "Reject the route update";
              }
            }
            description
              "Action to perform on matching routes.";
          }
          container set {
            leaf next-hop {
              type inet:ip-address;
              description
                "The next hop address.";
            }
            leaf ospf-metric-1 {
              type uint32;
              description
                "External Type-1 route metric.";
            }
            leaf ospf-metric-2 {
              type uint32;
              description
                "External Type-2 route metric.";
            }
            leaf bgp-as-path {
              type string;
              description
                "Sequence of AS numbers (separated by spaces) describing the AS path for this route.";
            }
            leaf bgp-local-preference {
              type uint32;
              description
                "Local preference value used for selection among multiple BGP routes.";
            }
            leaf bgp-med {
              type uint32;
              description
                "The Multiple Exit Discriminator is used on external (inter-AS) links
                 to convey to an adjacent AS the optimal entry point into the local AS.";
            }
          }
        }
      }
    }
    container static-routes {
      uses static-routes;
      description
        "Configuration of static routes.";
    }
    list routing-instance {
      key "name";
      description
        "Configuration of a routing instance.";
      leaf name {
        type string;
        description
          "The name of the routing instance.";
      }
      leaf description {
        type string;
        description
          "Textual description of the routing instance.";
      }
      container static-routes {
        uses static-routes;
        description
          "Configuration of static routes.";
      }
    }
    list rule {
      key "id";
      description
        "Configuration of a policy routing rule.";
      leaf id {
        type uint32;
        description
          "The order in which the rule is evaluated. Lower the value higher the priority.";
      }
      leaf-list classifier {
        min-elements 1;
        type leafref {
          path "/serv:services/qos:qos/qos:classifier/qos:name";
        }
        description
          "A list of classifers. If any of the classifiers
           match, then the traffic will be subjected to this rule.";
      }
      container action {
        choice action-type {
          mandatory true;
          case lookup {
            leaf lookup {
              type leafref {
                path "/routing/routing-instance/name";
              }
              description
                "Lookup the specified routing table.";
            }
          }
          case blackhole {
            leaf blackhole {
              type empty;
            }
            description
              "Drop packet silently.";
          }
          case unreachable {
            leaf unreachable {
              type empty;
            }
            description
              "Drop packet and generate icmp error \"network is reachable\".";
          }
          case prohibit {
            leaf prohibit {
              type empty;
            }
            description
              "Drop packet and generate icmp error \"communication is administratively prohibited\".";
          }
        }
      }
    }
  }

  grouping protocol-state {
    leaf routing-instance {
      type string;
      description
        "Routing instance name";
    }
    leaf state {
      type enumeration {
        enum "up";
        enum "down";
      }
      description
        "State of protocol.";
    }
    leaf preference {
      type uint16;
      description
        "Preference of routes generated by this protocol.";
    }
    leaf import-filter {
      type string;
      description
        "Import filter currently used by this protocol.";
    }
    leaf export-filter {
      type string;
      description
        "Export filter currently used by this protocol.";
    }
    container statistics {
      leaf import-updates-received {
        type uint32;
        description
          "Number of import route updates received.";
      }
      leaf import-updates-rejected {
        type uint32;
        description
          "Number of import route updates rejected as invalid.";
      }
      leaf import-updates-filtered {
        type uint32;
        description
          "Number of import route updates rejected by import filter.";
      }
      leaf import-updates-ignored {
        type uint32;
        description
          "Number of import route updates rejected as already in the route table.";
      }
      leaf import-updates-accepted {
        type uint32;
        description
          "Number of import route updates accepted and imported.";
      }
      leaf import-withdraws-received {
        type uint32;
        description
          "Number of import route withdraws received.";
      }
      leaf import-withdraws-rejected {
        type uint32;
        description
          "Number of import route withdraws rejected as invalid.";
      }
      leaf import-withdraws-ignored {
        type uint32;
        description
          "Number of import route withdraws ignored as already not in the route table.";
      }
      leaf import-withdraws-accepted {
        type uint32;
        description
          "Number of import route withdraws accepted and processed.";
      }
      leaf export-updates-received {
        type uint32;
        description
          "Number of export route updates accepted and processed.";
      }
      leaf export-updates-rejected {
        type uint32;
        description
          "Number of export route updates rejected by the protocol.";
      }
      leaf export-updates-filtered {
        type uint32;
        description
          "Number of export route updates rejected by the export filter.";
      }
      leaf export-updates-accepted {
        type uint32;
        description
          "Number of export route updates accepted and exported.";
      }
      leaf export-withdraws-received {
        type uint32;
        description
          "Number of export route withdraws received.";
      }
      leaf export-withdraws-accepted {
        type uint32;
        description
          "Number of export route withdraws accepted and processed.";
      }
    }
  }

  grouping routes {
    list routes {
      config false;
      leaf dest-prefix {
        type inet:ip-prefix;
        description
          "IP destination prefix.";
      }
      leaf next-hop {
        type inet:ip-address;
        description
          "IP address of the next hop.";
      }
      leaf outgoing-interface {
        type if:interface-ref;
        description
          "Outgoing interface.";
      }
      leaf source {
        type enumeration {
          enum "kernel" {
            description
              "Route has been added by the operating system based on interface configuration.";
          }
          enum "dynamic" {
            description
              "Route has been added by a dynamic routing protocol like RIP, OSPF";
          }
          enum "static" {
            description
              "Route has been added by the administrator via static configuration.";
          }
          enum "dhcp" {
            description
              "Route has been added by a DHCP.";
          }
          enum "ra" {
            description
              "Route has been added by a router advertisements.";
          }
        }
        description
          "The source of this route entry.";
      }
    }
  }

  container routing-state {
    config false;
    uses routes;
    list routing-instance {
      key "name";
      leaf name {
        type string;
        description
          "The name of the routing instance.";
      }
      uses routes;
    }
  }
}
