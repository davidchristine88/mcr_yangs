submodule mds-service-snmp-target {
  belongs-to mds-service-snmp {
    prefix snmp;
  }

  import mds-services {
    prefix serv;
  }
  import ietf-inet-types {
    prefix inet;
  }
  include mds-service-snmp-common;
  include mds-service-snmp-community;
  include mds-service-snmp-usm;

  reference
    "RFC3413: Simple Network Management Protocol (SNMP) Applications
     SNMP-TARGET-MIB";

  augment "/serv:services/snmp:snmp" {
    list target {
      key "name";
      description
        "List of targets";
      reference "SNMP-TARGET-MIB.snmpTargetAddrTable";
      leaf name {
        type snmp:identifier;
        description
          "identifies the target";
        reference "SNMP-TARGET-MIB.snmpTargetAddrName";
      }
      leaf ip {
        type inet:ip-address;
        mandatory true;
        description
          "Transport IP address of the target";
        reference
          "SNMP-TARGET-MIB.snmpTargetAddrTDomain
           SNMP-TARGET-MIB.snmpTargetAddrTAddress";
      }
      leaf port {
        type inet:port-number;
        default "162";
        description
          "UDP port number";
        reference
          "SNMP-TARGET-MIB.snmpTargetAddrTDomain
           SNMP-TARGET-MIB.snmpTargetAddrTAddress";
      }
      leaf-list tag {
        type snmp:identifier;
        description
          "List of tag values used to select target address";
        reference "SNMP-TARGET-MIB.snmpTargetAddrTagList";
      }
      leaf timeout {
        type uint32;
        units "0.01 seconds";
        default "1500";
        description
          "Needed only if this target can receive v3 informs.";
        reference "SNMP-TARGET-MIB.snmpTargetAddrTimeout";
      }
      leaf retries {
        type uint8;
        default "3";
        description
          "Needed only if this target can receive v3 informs.";
        reference "SNMP-TARGET-MIB.snmpTargetAddrRetryCount";
      }
      leaf engine-id {
        type leafref {
          path "/serv:services/snmp:snmp/usm/remote/engine-id";
        }
        must "/serv:services/snmp:snmp/usm/remote[engine-id=current()]/user[name=/serv:services/snmp:snmp/target[name=current()/../name]/usm/user-name]" {
          error-message
            "When engine-id is set, the usm/user-name must exist in the
             /serv:services/snmp:snmp/usm/remote list for this engine-id.";
        }
        description
          "Needed only if this target can receive v3 informs.
           
           This object is not present in the SNMP MIBs.  In
           RFC 3412s, it is a implementation specific matter how this engine-id
           is handled.";
        reference "RFC 3412 7.1.9a";
      }
      choice params {
        mandatory true;
        reference "SNMP-TARGET-MIB.snmpTargetParamsTable";
        container v1 {
          description
            "SNMPv1 parameters type";
          leaf sec-name {
            type leafref {
              path "/serv:services/snmp:snmp/community/sec-name";
            }
            mandatory true;
            reference "SNMP-TARGET-MIB.snmpTargetParamsSecurityName";
          }
        }
        container v2c {
          description
            "SNMPv2 community parameters type";
          leaf sec-name {
            type leafref {
              path "/serv:services/snmp:snmp/community/sec-name";
            }
            mandatory true;
            reference "SNMP-TARGET-MIB.snmpTargetParamsSecurityName";
          }
        }
        container usm {
          description
            "user based SNMPv3 parameters type";
          leaf user-name {
            type snmp:identifier;
            mandatory true;
            reference "SNMP-TARGET-MIB.snmpTargetParamsSecurityName";
          }
          leaf sec-level {
            type sec-level;
            mandatory true;
            reference "SNMP-TARGET-MIB.snmpTargetParamsSecurityLevel";
          }
        }
      }
    }
  }
  augment "/serv:services/snmp:snmp/snmp:community" {
    leaf target-tag {
      type leafref {
        path "/serv:services/snmp:snmp/target/tag";
      }
      description
        "Used to limit access for this community to the specified targets.";
      reference "SNMP-COMMUNITY-MIB.snmpCommunityTransportTag";
    }
  }
}
