submodule mds-service-snmp-vacm {
  belongs-to mds-service-snmp {
    prefix snmp;
  }

  import mds-services {
    prefix serv;
  }
  include mds-service-snmp-common;

  description
    "This submodule contains a collection of YANG definitions for 
     configuring the View-based Access Control Model (VACM) of 
     SNMP via NETCONF.";
  reference
    "RFC3415: View-based Access Control Model (VACM) for the
              Simple Network Management Protocol (SNMP)";

  typedef view-name {
    type snmp:identifier;
    description
      "The view-name type represents an SNMP VACM view name.";
  }

  typedef group-name {
    type snmp:identifier;
    description
      "The view-name type represents an SNMP VACM group name.";
  }

  grouping group-name {
    leaf group-name {
      type leafref {
        path "/serv:services/snmp:snmp/vacm/group/name";
      }
    }
  }

  augment "/serv:services/snmp:snmp" {
    container vacm {
      description
        "Configuration of the View-based Access Control Model";
      list group {
        key "name";
        description
          "VACM Groups";
        reference "SNMP-VIEW-BASED-ACM-MIB.vacmSecurityToGroupTable";
        leaf name {
          type group-name;
          description
            "The name of this VACM group.";
          reference "SNMP-VIEW-BASED-ACM-MIB.vacmGroupName";
        }
        list member {
          key "sec-name";
          min-elements 1;
          description
            "A member of this VACM group. According to VACM, every
             group must have at least one member.
             
             A certain combination of sec-name and sec-model MUST NOT
             be mapped to more than one group.";
          leaf sec-name {
            type snmp:sec-name;
            description
              "The securityName of a group member.";
          }
          leaf-list sec-model {
            type snmp:sec-model-no-wildcard;
            min-elements 1;
            description
              "The security models under which this securityName
               is a member of this group.";
          }
        }
        list access {
          key "sec-model sec-level";
          description
            "Definition of access right for groups";
          reference "SNMP-VIEW-BASED-ACM-MIB.vacmAccessTable";
          leaf context {
            if-feature multiple-contexts;
            type snmp:context-name;
            description
              "The context (prefix) under which the access rights apply.";
            reference "SNMP-VIEW-BASED-ACM-MIB.vacmAccessContextPrefix";
          }
          leaf context-match {
            if-feature multiple-contexts;
            type enumeration {
              enum "exact";
              enum "prefix";
            }
            default "exact";
            reference "SNMP-VIEW-BASED-ACM-MIB.vacmAccessContextMatch";
          }
          leaf sec-model {
            type snmp:sec-model;
            description
              "The security model under which the access rights apply.";
            reference "SNMP-VIEW-BASED-ACM-MIB.vacmAccessSecurityModel";
          }
          leaf sec-level {
            type snmp:sec-level;
            description
              "The minimum security level under which the access rights
               apply.";
            reference "SNMP-VIEW-BASED-ACM-MIB.vacmAccessSecurityLevel";
          }
          leaf read-view {
            type leafref {
              path "/serv:services/snmp:snmp/vacm/view/name";
            }
            description
              "The name of the MIB view of the SNMP context authorizing
               read access.";
            reference "SNMP-VIEW-BASED-ACM-MIB.vacmAccessReadViewName";
          }
          leaf write-view {
            type leafref {
              path "/serv:services/snmp:snmp/vacm/view/name";
            }
            description
              "The name of the MIB view of the SNMP context authorizing
               write access.";
            reference "SNMP-VIEW-BASED-ACM-MIB.vacmAccessWriteViewName";
          }
          leaf notify-view {
            type leafref {
              path "/serv:services/snmp:snmp/vacm/view/name";
            }
            description
              "The name of the MIB view of the SNMP context authorizing
               notify access.";
            reference "SNMP-VIEW-BASED-ACM-MIB.vacmAccessNotifyViewName";
          }
        }
      }
      list view {
        key "name";
        description
          "Definition of MIB views";
        reference "SNMP-VIEW-BASED-ACM-MIB.vacmViewTreeFamilyTable";
        leaf name {
          type view-name;
          description
            "The name of this VACM MIB view.";
          reference "SNMP-VIEW-BASED-ACM-MIB.vacmViewTreeFamilyName";
        }
        list subtree {
          key "oids";
          reference "SNMP-VIEW-BASED-ACM-MIB.vacmViewTreeFamilySubtree";
          leaf oids {
            type snmp:wildcard-object-identifier;
            description
              "A family of subtrees included in this MIB view.";
            reference
              "SNMP-VIEW-BASED-ACM-MIB.vacmViewTreeFamilySubtree
               SNMP-VIEW-BASED-ACM-MIB.vacmViewTreeFamilyMask";
          }
          choice type {
            mandatory true;
            reference "SNMP-VIEW-BASED-ACM-MIB.vacmViewTreeFamilyType";
            leaf included {
              type empty;
              description
                "The family of subtrees is included in the MIB view";
            }
            leaf excluded {
              type empty;
              description
                "The family of subtrees is excluded from the MIB view";
            }
          }
        }
      }
    }
  }
}
