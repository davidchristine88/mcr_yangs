submodule mds-service-snmp-community {
  belongs-to mds-service-snmp {
    prefix snmp;
  }

  import mds-services {
    prefix serv;
  }
  include mds-service-snmp-common;

  augment "/serv:services/snmp:snmp" {
    list community {
      key "index";
      description
        "List of communities";
      reference "SNMP-COMMUNITY-MIB.snmpCommunityTable";
      leaf index {
        type snmp:identifier;
        description
          "Index into the community list.";
        reference "SNMP-COMMUNITY-MIB.snmpCommunityIndex";
      }
      leaf name {
        type string;
        description
          "Use only when the community string is not the same as the index.";
        reference "SNMP-COMMUNITY-MIB.snmpCommunityName";
      }
      leaf sec-name {
        type snmp:sec-name;
        description
          "Initially set to the value of 'index'";
        mandatory true;
        reference "SNMP-COMMUNITY-MIB.snmpCommunitySecurityName";
      }
      leaf engine-id {
        if-feature snmp:proxy;
        type snmp:engine-id;
        description
          "If not set, the value of the local SNMP engine is operationally
           used by the device.";
        reference "SNMP-COMMUNITY-MIB.snmpCommunityContextEngineID";
      }
      leaf context {
        if-feature snmp:multiple-contexts;
        type snmp:context-name;
        default "";
        reference "SNMP-COMMUNITY-MIB.snmpCommunityContextName";
      }
    }
  }
}
